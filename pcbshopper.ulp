/**
 * @file pcbshopper.ulp
 * @brief Automatically parse PCB and submit for quote on PCBshopper.com
 *
 * @author Jeremy Ruhland <jeremy ( a t ) goopypanther.org>
 * @license (C) Jeremy Ruhland 2018 under GPL3
 *
 */

#usage "<b>PCBshopper Quote Helper</b>"
       "<p>"
       "Automatically submit quotes to PCBshopper.com"
       "<p>"
       "Get more information at <a href=\"http://github.com/JeremyRuhland/pcbshopper\">http://github.com/JeremyRuhland/pcbshopper</a>"
       "<author>Author: Jeremy Ruhland</author>"


// Defines
enum {
    false = 0,
    true  = 1
};

// Dimension units
enum {
    inches = 0,
    cm     = 1,
    mm     = 2
};

// Silkscreen/Stencils
enum {
    no     = 0,
    top    = 1,
    bottom = 2,
    both   = 3
};

// Mask
enum {
    none        = 0,
    least       = 1,
    black       = 2,
    blackmatte  = 3,
    blue        = 4,
    green       = 5,
    greenmatte  = 6,
    purple      = 7,
    red         = 8,
    transparent = 9,
    white       = 10,
    yellow      = 11
};

// Board thickness
enum {
    t24mil = 0,
    t31mil = 1,
    t40mil = 2,
    t47mil = 3,
    t62mil = 4,
    t79mil = 5
};

// Finish
enum {
    cheapest     = 0,
    cheapestRohs = 1,
    hasl         = 2,
    haslRohs     = 3,
    enig         = 4
};

// Quality certs
enum {
    na       = 0,
    iso9001  = 1,
    ipc600   = 2,
    either   = 3,
    qualBoth = 4
};
//

// User generated layers
enum {
    LAYER_TSILK = 121,
    LAYER_BSILK = 122
};


// Global variables
string Version = "1";
string paramWarnings;

// String arrays for dialog dropdown menus
string solderMaskArray[] = {
    "None",
    "Least expensive",
    "Black",
    "Matte Black",
    "Blue",
    "Green",
    "Matte Green",
    "Purple",
    "Red",
    "Transparent",
    "White",
    "Yellow"
};

string boardThicknessArray[] = {
    "0.6mm/24mil",
    "0.8mm/31mil",
    "1.0mm/40mil",
    "1.2mm/47mil",
    "1.6mm/62mil",
    "2.0mm/79mil"
};

string finishTypeArray[] = {
    "Cheapest",
    "Cheapest RoHS",
    "HASL",
    "HASL RoHS",
    "ENIG RoHS"
};

string copperWeightArray[] = {
    "1oz",
    "2oz",
    "3oz",
    "4oz",
    "5oz",
    "6oz"
};

string stencilOptionArray[] = {
    "None",
    "One side",
    "Both sides"
};

string qualityOptionArray[] = {
    "N/A",
    "ISO-9001",
    "IPC-600",
    "Either",
    "Both"
};

string countryArray[] = {
    "AF", "AX", "AL", "DZ", "AS", "AD", "AO", "AI",
    "AG", "AR", "AM", "AW", "AU", "AT", "AZ", "BS",
    "BH", "BD", "BB", "BY", "BE", "BZ", "BJ", "BM",
    "BT", "BO", "BQ", "BA", "BW", "BV", "BR", "IO",
    "BN", "BG", "BF", "BI", "KH", "CM", "CA", "CV",
    "KY", "CF", "TD", "CL", "CN", "CX", "CC", "CO",
    "KM", "CG", "CD", "CK", "CR", "CI", "HR", "CW",
    "CY", "CZ", "DK", "DJ", "DM", "DO", "EC", "EG",
    "SV", "GQ", "ER", "EE", "ET", "FK", "FO", "FJ",
    "FI", "FR", "GF", "PF", "GA", "GM", "GE", "DE",
    "GH", "GI", "GR", "GL", "GD", "GP", "GU", "GT",
    "GG", "GN", "GW", "GY", "HT", "VA", "HN", "HK",
    "HU", "IS", "IN", "ID", "IR", "IQ", "IE", "IM",
    "IL", "IT", "JM", "JP", "JE", "JO", "KZ", "KE",
    "KI", "KR", "KW", "KG", "LA", "LV", "LB", "LS",
    "LR", "LY", "LI", "LT", "LU", "MO", "MK", "MG",
    "MW", "MY", "MV", "ML", "MT", "MH", "MQ", "MR",
    "MU", "YT", "MX", "FM", "MD", "MC", "MN", "ME",
    "MS", "MA", "MZ", "MM", "NA", "NR", "NP", "NL",
    "NC", "NZ", "NI", "NE", "NG", "NU", "NF", "MP",
    "NO", "OM", "PK", "PW", "PS", "PA", "PG", "PY",
    "PE", "PH", "PN", "PL", "PT", "PR", "QA", "RE",
    "RO", "RU", "RW", "BL", "SH", "KN", "LC", "MF",
    "PM", "VC", "WS", "SM", "ST", "SA", "SN", "RS",
    "SC", "SL", "SG", "SX", "SK", "SI", "SB", "SO",
    "ZA", "GS", "SS", "ES", "LK", "SD", "SR", "SJ",
    "SZ", "SE", "CH", "SY", "TW", "TJ", "TZ", "TH",
    "TL", "TG", "TK", "TO", "TT", "TN", "TR", "TM",
    "TC", "TV", "UG", "UA", "AE", "GB", "US", "UY",
    "UZ", "VU", "VE", "VN", "VG", "VI", "WF", "EH",
    "YE", "ZM", "ZW"
};

string leadTimeArray[] = {
    "default", "2", "3",
    "4", "5", "6", "7",
    "8", "9", "10", "11",
    "12", "13", "14", "15",
    "16", "17", "18", "19",
    "20", "21", "22", "23",
    "24", "25", "26", "27",
    "28", "29", "30"
};

string quantityArray[] = {
    "1", "2", "3", "4", "5",
    "6", "7", "8", "9", "10",
    "Select qty on PCBShopper.com"
};

// Params for API
real pcbShopperWidth; // Board width
real pcbShopperHeight; // Board height
char pcbShopperUnits; // Dim measurement units
int pcbShopperLayers; // Board layers
int pcbShopperSolderMaskColor; // Solder mask color, unimplemented, no good way to get data from eagle
int pcbShopperBoardThickness; // Board thickness
int pcbShopperSilkscreen; // Silkscreen number
int pcbShopperCopperFinishType; // Copper finish type, unimplemented, assumed cheapest
int pcbShopperCopperWeightOz; // Copper weight, 0 indexed for 1oz, unimplemented, parsing dru files too annoying
real pcbShopperTrace; // Min trace thickness
int pcbShopperTwUnits; // Trace thickness units
real pcbShopperDrill; // Min drill size
int pcbShopperDrillUnits; // Drill size units
int pcbShopperFingers; // Number of hard gold finish parts
int pcbShopperStencil; // Stencil, unimplemented, assumed no
int pcbShopperQuality; // Quality, unimplemented, assumed not required
int pcbShopperDesigns; // Designs, unimplemented, assumed 1
int pcbShopperQuantity; // Quantity, unimplemented, 0 indxed for qty 1, assumed 3
string pcbShopperCountry; // Country, unimplemented, assumed US
int pcbShopperDays; // Days, unimplemented, assumed default


// Functions

/**
 * Turn int into string
 *
 * @param num Int to string
 * @return String containing int
 */
string int2String(int num) {
    string retString;

    sprintf(retString, "%d", num);

    return (retString);
}


/**
 * Turn float into string
 *
 * @param num Float to string
 * @return String containing float
 */
string float2String(real num) {
    string retString;

    sprintf(retString, "%f", num);

    return (retString);
}


/**
 * Wrap string in list tags
 *
 * @param item String to wrap
 * @return Wrapped string
 */
string listWrap(string item) {
    return ("<li>" + item + "</li>");
}


/**
 * Make string bold
 *
 * @param str String to bold
 * @return Bold'd string
 */
string string2Bold(string str) {

    return ("<b>" + str + "</b>");
}


/**
 * Assemble URL string for pcbshopper.com quote
 *
 * @return URL string
 */
string assembleQuoteUrl(void) {
    string quoteString;

    string stringUnits;
    string stringTWUnits;
    string stringDrillUnits;
    string stringSolderMaskColor;
    string stringFinish;
    string stringBoardThickness;
    int intStencil;
    string stringQuality;
    string stringCountry;
    string stringDays;

    // Create string for units
    switch (pcbShopperUnits) {
    case inches:
        stringUnits = "inches";
        break;
    case cm:
        stringUnits = "cm";
        break;
    case mm:
        stringUnits = "mm";
        break;
    default:
        stringUnits = "err";
        break;
    }

    // Create string for trace width units
    switch (pcbShopperTwUnits) {
    case inches:
        stringTWUnits = "inches";
        break;
    case cm:
        stringTWUnits = "cm";
        break;
    case mm:
        stringTWUnits = "mm";
        break;
    default:
        stringTWUnits = "err";
        break;
    }

    // Create string for drill width units
    switch (pcbShopperDrillUnits) {
    case inches:
        stringDrillUnits = "inches";
        break;
    case cm:
        stringDrillUnits = "cm";
        break;
    case mm:
        stringDrillUnits = "mm";
        break;
    default:
        stringDrillUnits = "err";
        break;
    }

    // Create string for soldermask color
    switch (pcbShopperSolderMaskColor) {
    case none:
        stringSolderMaskColor = "nomask";
        break;
    case least:
        stringSolderMaskColor = "cheapest";
        break;
    case black:
        stringSolderMaskColor = "black";
        break;
    case blackmatte:
        stringSolderMaskColor = "blackmatte";
        break;
    case blue:
        stringSolderMaskColor = "blue";
        break;
    case green:
        stringSolderMaskColor = "green";
        break;
    case greenmatte:
        stringSolderMaskColor = "greenmatte";
        break;
    case purple:
        stringSolderMaskColor = "purple";
        break;
    case red:
        stringSolderMaskColor = "red";
        break;
    case transparent:
        stringSolderMaskColor = "transparent";
        break;
    case white:
        stringSolderMaskColor = "white";
        break;
    case yellow:
        stringSolderMaskColor = "yellow";
        break;
    default:
        stringSolderMaskColor = "err";
        break;
    }

    // Create string for surface finish
    switch (pcbShopperCopperFinishType) {
    case cheapest:
        stringFinish = "cheapest";
        break;
    case cheapestRohs:
        stringFinish = "cheapestLF";
        break;
    case hasl:
        stringFinish = "HASL";
        break;
    case haslRohs:
        stringFinish = "Lead-free%20HASL";
        break;
    case enig:
        stringFinish = "ENIG";
        break;
    default:
        stringFinish = "err";
        break;
    }

    // Create string for board thickness
    switch (pcbShopperBoardThickness) {
    case t24mil:
        stringBoardThickness = "0.6";
        break;
    case t31mil:
        stringBoardThickness = "0.8";
        break;
    case t40mil:
        stringBoardThickness = "1.0";
        break;
    case t47mil:
        stringBoardThickness = "1.2";
        break;
    case t62mil:
        stringBoardThickness = "1.6";
        break;
    case t79mil:
        stringBoardThickness = "2.0";
        break;
    default:
        stringBoardThickness = "err";
        break;
    }

    // Create string for quality
    switch (pcbShopperQuality) {
    case na:
        stringQuality = "Any";
        break;
    case iso9001:
        stringQuality = "iso9001";
        break;
    case ipc600:
        stringQuality = "ipc600";
        break;
    case either:
        stringQuality = "either";
        break;
    case qualBoth:
        stringQuality = "both";
        break;
    default:
        stringQuality = "err";
        break;
    }

    // Create string for days lead time
    if (pcbShopperDays > 0) {
        stringDays = int2String(pcbShopperDays + 1); // Lead time options skip 1, so we count over it
    } else {
        stringDays = "default";
    }

    sprintf(quoteString, "http://pcbshopper.com/?Width=%f&Height=%f&Units=%s&" +
            "Layers=%d&Color=%s&Silkscreen=%d&Finish=%s&Thickness=%s&Cu=%d&" +
            "Trace=%f&TWUnits=%s&Drill=%f&DrillUnits=%s&Fingers=%d&" +
            "Stencil=%d&Quality=%s&Designs=%d&Quantity=%d&Country=%s&days=%s",
            pcbShopperWidth, pcbShopperHeight, stringUnits, pcbShopperLayers,
            stringSolderMaskColor, pcbShopperSilkscreen, stringFinish,
            stringBoardThickness, (pcbShopperCopperWeightOz + 1),
            pcbShopperTrace, stringTWUnits, pcbShopperDrill, stringDrillUnits,
            pcbShopperFingers, pcbShopperStencil, stringQuality,
            pcbShopperDesigns, (pcbShopperQuantity + 1),
            pcbShopperCountry, stringDays);

    quoteString = "<a href=\"" + quoteString + "\"> Click Here To Open PCBShopper.com</a>";

    return (quoteString);
}


/**
 * Calculate PCB parameters required for quote
 *
 * Currently calculates (in order):
 *  1. Copper layer count
 *  2. Silkscreen layer usage
 *  3. Outer board dimensions using board outline layer
 *      (taking into account wire width)
 *  4. Minimum trace width
 *  5. Smallest drill size
 *  6. Unrouted nets
 *  7. Hard gold finish objects
 *  8. Defauls for solder mask color, copper finish type, copper weight,
 *      stencil, quality options, design number, country and speed
 *
 * Everything is stored into pcbShopper global variables, mm where applicable
 */
void calculateParams(void) {
    char tSilk = false;
    char bSilk = false;
    char tFinish = false;
    char bFinish = false;

    // Check layer usage
    board(B) { // Create board context for layer usage check
        B.layers(L) { // Loop context for each layer
            // Count each copper layer used
            if ((L.number <= 16) && (L.used == true)) {
                pcbShopperLayers++;
            // Catch silk layers
            } else if (((L.number == LAYER_TPLACE) || (L.number == LAYER_TSILK)) && (L.used == true)) {
                tSilk = true;
            } else if (((L.number == LAYER_BPLACE) || (L.number == LAYER_BSILK)) && (L.used == true)) {
                bSilk = true;
            } else {}
        }
    }

    if ((tSilk == true) && (bSilk == true)) {
        pcbShopperSilkscreen = both;
    } else if (tSilk == true) {
        pcbShopperSilkscreen = top;
    } else if (bSilk == true) {
        pcbShopperSilkscreen = bottom;
    } else {
        pcbShopperSilkscreen = no;
    }

    if (pcbShopperLayers == 0) {
        paramWarnings += listWrap("No traces found on copper layers.");
    } else {}

    // Measure board dims from outline
    int xMin, xMax, yMin, yMax;
    char initialObj = true;


    board(B) { // Create board context
        B.layers(L) { // Loop for each layer
            // If dimension layer is unused, generate warning
            if ((L.number == LAYER_DIMENSION) && (L.used == false)) {
                paramWarnings += listWrap("No dimension layer found, board must have dimension for quote.");
            } else {}
        }

        B.wires(W) { // Loop through wires
            // If wire is on dimension layer
            if (W.layer == LAYER_DIMENSION) {
                if (initialObj == true) { // Catch initial wire so min/max is init'd *somewhere* on board edge
                    initialObj = false;

                    xMin = W.x1;
                    yMin = W.y1;

                    xMax = W.x1;
                    yMax = W.y1;
                } else {}

                xMin = min(xMin, (W.x1 - (W.width / 2)));
                xMin = min(xMin, (W.x2 - (W.width / 2)));

                xMax = max(xMax, (W.x1 + (W.width / 2)));
                xMax = max(xMax, (W.x2 + (W.width / 2)));

                yMin = min(yMin, (W.y1 - (W.width / 2)));
                yMin = min(yMin, (W.y2 - (W.width / 2)));

                yMax = max(yMax, (W.y1 + (W.width / 2)));
                yMax = max(yMax, (W.y2 + (W.width / 2)));

                // If wire is an arc additional checks must be performed to find actual min/max
                if (W.arc) { // If wire is arc, calculate bounding box of arc
                    xMin = min(xMin, (W.arc.xc - W.arc.radius - (W.arc.width / 2)));
                    yMin = min(yMin, (W.arc.yc - W.arc.radius - (W.arc.width / 2)));

                    xMax = max(xMax, (W.arc.xc + W.arc.radius + (W.arc.width / 2)));
                    yMax = max(yMax, (W.arc.yc + W.arc.radius + (W.arc.width / 2)));
                } else {}
            } else {}
        }

        // In the event the board outline is made of a single circle...
        B.circles(C) { // Loop through circles
            if (C.layer == LAYER_DIMENSION) {
                if (initialObj == true) { // Catch initial object so min/max starts at center of board
                    initialObj = false;

                    xMin = C.x;
                    yMin = C.y;

                    xMax = C.x;
                    yMax = C.y;
                } else {}

                // Check against min/max so internal circular cutouts don't overwrite actual board edge
                xMin = min(xMin, (C.x - C.radius - (C.width / 2)));
                yMin = min(yMin, (C.y - C.radius - (C.width / 2)));

                xMax = max(xMax, (C.x + C.radius + (C.width / 2)));
                yMax = max(yMax, (C.y + C.radius + (C.width / 2)));
            }
        }
    }

    // Find board dims from min/max points & convert internal units to mm
    pcbShopperWidth = u2mm(xMax - xMin);
    pcbShopperHeight = u2mm(yMax - yMin);
    pcbShopperUnits = mm;

    // Find minimum trace width
    int smallestTrace = INT_MAX; // Will lose to any other real trace

    board(B) { // Board context
        B.signals(S) { // Loop through all signals
            S.wires(W) { // Loop through each wire
                if (W.layer <= 16) { // Check if on copper layers
                    smallestTrace = min(smallestTrace, W.width); // Find thinest trace
                } else {}
            }

            /* Check S.polygons for width? Thinking no, poly width not correlated to
             * actual width, ie. zero width polygons
             */
        }

        B.wires(W) { // Loop through all wires
            if (W.layer <= 16) { // Check if on copper layers
                smallestTrace = min(smallestTrace, W.width); // Find thinest trace
            } else {}
        }
    }

    pcbShopperTrace = u2mm(smallestTrace); // Convert internal units to mm
    pcbShopperTwUnits = mm;

    // Check hole sizes
    int smallestHole = INT_MAX; // Will lose to any other real hole

    board(B) { // Board context
        B.holes(H) { // Loop through board holes
            smallestHole = min(smallestHole, H.drill); // Find smallest drill
        }

        B.signals(S) {
            S.vias(V) {
                smallestHole = min(smallestHole, V.drill); // Find any via smaller than hole
            }
        }

        B.elements(E) { // Loop through each object on PCB
            E.package.contacts(C) { // Loop through each contact of each package
                if (C.pad) {
                    smallestHole = min(smallestHole, C.pad.drill); // Find contacts smaller than hole
                } else {}
            }

            E.package.holes(H) { // Loop through holes in each package
                smallestHole = min(smallestHole, H.drill); // Find holes smaller than others
            }
        }
    }

    pcbShopperDrill = u2mm(smallestHole); // Convert internal units to mm
    pcbShopperDrillUnits = mm;

    // Check for unrouted nets
    char ratsnestExist = false;

    board(B) { // Board context
        B.wires(W) { // Loop & check for unrouted wires
            if (W.layer == LAYER_UNROUTED) {
                ratsnestExist = true;
            } else {}
        }

        B.signals(S) {
            S.wires(W) { // Loop & check for unrouted signal wires
                if (W.layer == LAYER_UNROUTED) {
                    ratsnestExist = true;
                } else {}
            }

            S.polygons(P) { // Loop & check for unrouted polygons
                if (P.layer == LAYER_UNROUTED) {
                    ratsnestExist = true;
                } else {}
            }
        }
    }

    if (ratsnestExist == true) {
        paramWarnings += listWrap("There are unrouted nets on the PCB.");
    } else {}

    // Count hard gold finish pads (just the polygons and rectangles)
    char finishLayersUsed = false;
    pcbShopperFingers = 0;

    board(B) { // Board context
        // Check if either finish layer used
        B.layers(L) { // Loop through each layer
            if ((L.number == LAYER_TFINISH) || (L.number == LAYER_BFINISH)) {
                finishLayersUsed = true;
            } else {}
        }

        // Only run further counts if finish layers were used
        if (finishLayersUsed) {
            B.elements(E) { // Loop through each object
                E.package.polygons(P) { // Loop through each polygon of each package
                    if ((P.layer == LAYER_TFINISH) || (P.layer == LAYER_BFINISH)) {
                        pcbShopperFingers++;
                    } else {}
                }

                E.package.rectangles(R) { // Loop through each rectangle of each package
                    if ((R.layer == LAYER_TFINISH) || (R.layer == LAYER_BFINISH)) {
                        pcbShopperFingers++;
                    } else {}
                }
            }

            B.polygons(P) { // Loop through each polygon
                if ((P.layer == LAYER_TFINISH) || (P.layer == LAYER_BFINISH)) {
                    pcbShopperFingers++;
                } else {}
            }

            B.rectangles(R) { // Loop through each rectangle
                if ((R.layer == LAYER_TFINISH) || (R.layer == LAYER_BFINISH)) {
                    pcbShopperFingers++;
                } else {}
            }

            B.circles(C) { // Loop through each circle
                if ((C.layer == LAYER_TFINISH) || (C.layer == LAYER_BFINISH)) {
                    pcbShopperFingers++;
                } else {}
            }
        } else {}
    }

    pcbShopperSolderMaskColor = least;
    pcbShopperCopperFinishType = cheapest;
    pcbShopperCopperWeightOz = 0; // 1oz
    pcbShopperStencil = no;
    pcbShopperQuality = na; // No quality check
    pcbShopperDesigns = 1;
    pcbShopperQuantity = 2; // So OSHpark is alway an option
    pcbShopperCountry = "US"; // Assumed US
    pcbShopperDays    = 0; // Default
}


/**
 * Draw dialog with quote information
 */
void drawDialog(void) {
    string quoteUrl;

    int solderMaskArrayIndex;
    int finishTypeArrayIndex;
    int copperWeightArrayIndex;
    int stencilOptionArrayIndex;
    int qualityOptionArrayIndex;
    int countryArrayIndex = 230; // Default to US
    int boardThicknessArrayIndex = t62mil; // Default to 1.6mm/62mil
    int leadTimeArrayIndex;

    dlgDialog("PCBShopper Quote Generator V" + Version) {
        quoteUrl = assembleQuoteUrl();

        dlgHBoxLayout {
            dlgSpacing(600);
        }

        dlgGroup("Notice") {
            dlgLabel("This script will create a quote for your PCB on PCBShopper.com. Some details related to your<br>" +
                     "board cannot be pulled automatically from your design and can be manually selected from the drop-downs below " +
                     "or on PCBShopper.com after clicking the link." +
                     "<p>This script was written by <a href=\"http://goopypanther.org\">Jeremy Ruhland</a> and released as GPL 3.0.<br>You can fork the project or submit bugfixes <a href=\"https://github.com/JeremyRuhland/pcbshopper\">on its github page.</a>");
        }

        if (paramWarnings) {
            dlgGroup("Warnings:") {
                dlgLabel(paramWarnings);
            }
        } else {}

        dlgGroup("Params:") {
            dlgGridLayout {
                dlgCell(0, 0) {
                    dlgLabel(string2Bold("Width:"));
                }

                dlgCell(0, 1) {
                    dlgLabel(float2String(pcbShopperWidth) + " mm");
                }

                dlgCell(1, 0) {
                    dlgLabel(string2Bold("Height:"));
                }

                dlgCell(1, 1) {
                    dlgLabel(float2String(pcbShopperHeight) + " mm");
                }

                dlgCell(2, 0) {
                    dlgLabel(string2Bold("Layer Count:"));
                }

                dlgCell(2, 1) {
                    dlgLabel(int2String(pcbShopperLayers));
                }

                dlgCell(3, 0) {
                    dlgLabel(string2Bold("Solder Mask Color:"));
                }

                dlgCell(3, 1) {
                    dlgComboBox(solderMaskArray, pcbShopperSolderMaskColor) {
                        quoteUrl = assembleQuoteUrl(); // Update quote link using new selection
                        dlgRedisplay(); // Update dialog
                    }
                }

                dlgCell(4, 0) {
                    dlgLabel(string2Bold("Silkscreen:"));
                }

                dlgCell(4, 1) {
                    switch (pcbShopperSilkscreen) {
                    case no:
                        dlgLabel("None");
                        break;
                    case top:
                        dlgLabel("Top");
                        break;
                    case bottom:
                        dlgLabel("Bottom");
                        break;
                    case both:
                        dlgLabel("Top & Bottom");
                        break;
                    default:
                        dlgLabel("Err");
                        break;
                    }
                }

                dlgCell(5, 0) {
                    dlgLabel(string2Bold("Finish Type:"));
                }

                dlgCell(5, 1) {
                    dlgComboBox(finishTypeArray, pcbShopperCopperFinishType) {
                        quoteUrl = assembleQuoteUrl(); // Update quote link using new selection
                        dlgRedisplay(); // Update dialog
                    }
                }

                dlgCell(6, 0) {
                    dlgLabel(string2Bold("Board Thickness:"));
                }
 
                dlgCell(6, 1) {
                    dlgComboBox(boardThicknessArray, boardThicknessArrayIndex) {
                        pcbShopperBoardThickness = boardThicknessArrayIndex; // Select new board thickness from array

                        quoteUrl = assembleQuoteUrl(); // Update quote link using new selection
                        dlgRedisplay(); // Update dialog
                    }
                }

                dlgCell(7, 0) {
                    dlgLabel(string2Bold("Copper Weight (Outer Layers):"));
                }

                dlgCell(7, 1) {
                    dlgComboBox(copperWeightArray, pcbShopperCopperWeightOz) {
                        quoteUrl = assembleQuoteUrl(); // Update quote link using new selection
                        dlgRedisplay(); // Update dialog
                    }
                }

                dlgCell(8, 0) {
                    dlgLabel(string2Bold("Min Trace Width:"));
                }

                dlgCell(8, 1) {
                    dlgLabel(float2String(pcbShopperTrace) + " mm");
                }

                dlgCell(9, 0) {
                    dlgLabel(string2Bold("Min Drill:"));
                }

                dlgCell(9, 1) {
                    dlgLabel(float2String(pcbShopperDrill) + " mm");
                }

                dlgCell(10, 0) {
                    dlgLabel(string2Bold("Plated Gold Fingers:"));
                }

                dlgCell(10, 1) {
                    dlgLabel(int2String(pcbShopperFingers));
                }

                dlgCell(11, 0) {
                    dlgLabel(string2Bold("Stencil Option:"));
                }

                dlgCell(11, 1) {
                    dlgComboBox(stencilOptionArray, pcbShopperStencil) {
                        quoteUrl = assembleQuoteUrl(); // Update quote link using new selection
                        dlgRedisplay(); // Update dialog
                    }
                }

                dlgCell(12, 0) {
                    dlgLabel(string2Bold("Quality Option:"));
                }

                dlgCell(12, 1) {
                    dlgComboBox(qualityOptionArray, pcbShopperQuality) {
                        quoteUrl = assembleQuoteUrl(); // Update quote link using new selection
                        dlgRedisplay(); // Update dialog
                    }
                }

                dlgCell(13, 0) {
                    dlgLabel(string2Bold("Quantity:"));
                }

                dlgCell(13, 1) {
                    dlgComboBox(quantityArray, pcbShopperQuantity) {
                        quoteUrl = assembleQuoteUrl(); // Update quote link using new selection
                        dlgRedisplay(); // Update dialog
                    }
                }

                dlgCell(14, 0) {
                    dlgLabel(string2Bold("Country:"));
                }

                dlgCell(14, 1) {
                    dlgComboBox(countryArray, countryArrayIndex) {
                        pcbShopperCountry = countryArray[countryArrayIndex]; // Select new country code from array

                        quoteUrl = assembleQuoteUrl(); // Update quote link using new selection
                        dlgRedisplay(); // Update dialog
                    }
                }

                dlgCell(15, 0) {
                    dlgLabel(string2Bold("Lead Time (Business Days):"));
                }

                dlgCell(15, 1) {
                    dlgComboBox(leadTimeArray, leadTimeArrayIndex) {
                        pcbShopperDays = leadTimeArrayIndex;

                        quoteUrl = assembleQuoteUrl(); // Update quote link using new selection
                        dlgRedisplay(); // Update dialog
                    }
                }
            }
        }

        dlgGroup("Quote:") {
            dlgHBoxLayout {
                dlgLabel(quoteUrl, 1);

                dlgStretch(1);

                dlgPushButton("&Close") {
                    dlgAccept();
                }
            }
        }
    };
}


/*
 * Main function executed from here
 */

// Check we are in layout editor...
if (board) {
    status("Identifying PCB design constraints...");
    calculateParams(); // Check PCB for all relevant design constraints

    // Check if any warnings were generated during param calcs
    if (paramWarnings) {
        // Generate warning string for display
        paramWarnings = "<b>Warnings generated during param calcs:</b> <ul>" + paramWarnings + "</ul>";
    } else {}

    drawDialog(); // Display info dialog with params

    exit(EXIT_SUCCESS);

// If we are not in layout editor...
} else {
    // Popup warning
    dlgMessageBox("This script must be run from layout editor.");
}
